; ## genutils

; Various General Utilities

; ## (polyline-vertexlist)
; Returns a list of 3dpoints consisting of vertices of a polyline
; * 1. a polyline entity

; * returns a list 3dpoints , defining vertices of given polyline

(defun get-polyline-vertices (ent) 
  (setq vlist nil)
  (if (and ent (eq (cdr (assoc 0 (entget ent))) "POLYLINE")) 
    (setq vlist (get-3dpolyline-vertices ent))
  )
  (if (and ent (eq (cdr (assoc 0 (entget ent))) "LWPOLYLINE")) 
    (setq vlist (get-lwpolyline-vertices ent))
  )
  vlist;
)

(defun get-3dpolyline-vertices (ent) 
  (if (and ent (eq (cdr (assoc 0 (entget ent))) "POLYLINE")) 

    (progn 
      (setq vlist '(nil))
      (setq subent (entnext ent))
      (while subent 
        (if (eq (cdr (assoc 0 (entget subent))) "VERTEX") 
          (setq vlist (append vlist (list (cdr (assoc 10 (entget subent))))))
        )
        (setq subent (entnext subent))
      )
      (setq vlist (cdr vlist))
    )
    (progn 
      (setq vlist -1)
    )
  )
  vlist ;
)


(defun get-lwpolyline-vertices (ent) 
  (if (and ent (eq (cdr (assoc 0 (entget ent))) "LWPOLYLINE")) 
    (progn 
      (setq vlist '(nil))
      (setq edata (entget ent))
      (setq cnt 0)
      (while (< cnt (length edata)) 
        (setq chunk (nth cnt edata))
        (if (= (car chunk) 10) 
          (setq vlist (append vlist (list (cdr chunk))))
        )
        (setq cnt (1+ cnt))
      )
      (setq vlist (cdr vlist))
    )
    (progn 
      (setq vlist -1)
    )
  )
  vlist ;
)


  ; ((-1 . <Entity name: 1d27da604d0>)
  ;   (0 . "LWPOLYLINE")
  ;   (330 . <Entity name: 1d27da5c1f0>)
  ;   (5 . "20D")
  ;   (100 . "AcDbEntity")
  ;   (67 . 0)
  ;   (410 . "Model")
  ;   (8 . "0")
  ;   (100 . "AcDbPolyline")
  ;   (90 . 9)
  ;   (70 . 0)
  ;   (43 . 0.0)
  ;   (38 . 0.0)
  ;   (39 . 0.0)
  ;   (10 16.4226 10.649)
  ;   (40 . 0.0)
  ;   (41 . 0.0)
  ;   (42 . 0.0)
  ;   (91 . 0)
  ;   (10 24.7476 16.5452)
  ;   (40 . 0.0)
  ;   (41 . 0.0)
  ;   (42 . 0.0)
  ;   (91 . 0)
  ;   (10 32.5623 14.4098)
  ;   (40 . 0.0)
  ;   (41 . 0.0)
  ;   (42 . 0.0)
  ;   (91 . 0)
  ;   (10 37.1236 10.9677)
  ;   (40 . 0.0)
  ;   (41 . 0.0)
  ;   (42 . 0.0)
  ;   (91 . 0)
  ;   (10 43.7581 14.5692)
  ;   (40 . 0.0)
  ;   (41 . 0.0)
  ;   (42 . 0.0)
  ;   (91 . 0)
  ;   (10 40.2494 18.8081)
  ;   (40 . 0.0)
  ;   (41 . 0.0)
  ;   (42 . 0.0)
  ;   (91 . 0)
  ;   (10 32.7218 19.9236)
  ;   (40 . 0.0)
  ;   (41 . 0.0)
  ;   (42 . 0.0)
  ;   (91 . 0)
  ;   (10 19.4847 20.9754)
  ;   (40 . 0.0)
  ;   (41 . 0.0)
  ;   (42 . 0.0)
  ;   (91 . 0)
  ;   (10 12.6269 18.2663)
  ;   (40 . 0.0)
  ;   (41 . 0.0)
  ;   (42 . 0.0)
  ;   (91 . 0)
  ;   (210 0.0 0.0 1.0)
  ; )
